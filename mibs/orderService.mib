ORDER-SERVICE-MIB DEFINITIONS ::= BEGIN

IMPORTS
    OBJECT-TYPE
        FROM SNMPv2-SMI
    Integer32
        FROM SNMPv2-SMI
    enterprises
        FROM SNMPv2-SMI;

orderService   OBJECT IDENTIFIER ::= { enterprises 55556 }

ordersPerMin OBJECT-TYPE
    SYNTAX      Integer32
    MAX-ACCESS  read-only
    STATUS      current
    DESCRIPTION "Orders per minute."
    ::= { orderService 1 }

orderUpdateRate OBJECT-TYPE
    SYNTAX      Integer32
    MAX-ACCESS  read-only
    STATUS      current
    DESCRIPTION "Order update rate per minute."
    ::= { orderService 2 }

orderFailureRate OBJECT-TYPE
    SYNTAX      Integer32
    MAX-ACCESS  read-only
    STATUS      current
    DESCRIPTION "Order failure rate percentage."
    ::= { orderService 3 }

avgOrderProcessingMs OBJECT-TYPE
    SYNTAX      Integer32
    MAX-ACCESS  read-only
    STATUS      current
    DESCRIPTION "Average order processing time milliseconds."
    ::= { orderService 4 }

activeOrders OBJECT-TYPE
    SYNTAX      Integer32
    MAX-ACCESS  read-only
    STATUS      current
    DESCRIPTION "Number of active orders."
    ::= { orderService 5 }

END
