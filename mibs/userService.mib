USER-SERVICE-MIB DEFINITIONS ::= BEGIN

IMPORTS
    OBJECT-TYPE
        FROM SNMPv2-SMI
    Integer32
        FROM SNMPv2-SMI
    enterprises
        FROM SNMPv2-SMI;

userService     OBJECT IDENTIFIER ::= { enterprises 55555 }

activeUsers OBJECT-TYPE
    SYNTAX      Integer32
    MAX-ACCESS  read-only
    STATUS      current
    DESCRIPTION "Number of active users currently logged in."
    ::= { userService 1 }

authSuccessRate OBJECT-TYPE
    SYNTAX      Integer32
    MAX-ACCESS  read-only
    STATUS      current
    DESCRIPTION "Percentage of successful authentication."
    ::= { userService 2 }

authFailureRate OBJECT-TYPE
    SYNTAX      Integer32
    MAX-ACCESS  read-only
    STATUS      current
    DESCRIPTION "Percentage of failed authentication."
    ::= { userService 3 }

avgLoginResponseMs OBJECT-TYPE
    SYNTAX      Integer32
    MAX-ACCESS  read-only
    STATUS      current
    DESCRIPTION "Average login response time in milliseconds."
    ::= { userService 4 }

profileUpdateRate OBJECT-TYPE
    SYNTAX      Integer32
    MAX-ACCESS  read-only
    STATUS      current
    DESCRIPTION "Profile update rate in updates per minute."
    ::= { userService 5 }

END
