NOTIFICATION-SERVICE-MIB DEFINITIONS ::= BEGIN

IMPORTS
    OBJECT-TYPE
        FROM SNMPv2-SMI
    Integer32
        FROM SNMPv2-SMI
    enterprises
        FROM SNMPv2-SMI;

notificationService OBJECT IDENTIFIER ::= { enterprises 55559 }

notificationsPerMin OBJECT-TYPE
    SYNTAX      Integer32
    MAX-ACCESS  read-only
    STATUS      current
    DESCRIPTION "Notifications per minute."
    ::= { notificationService 1 }

notificationFailureRate OBJECT-TYPE
    SYNTAX      Integer32
    MAX-ACCESS  read-only
    STATUS      current
    DESCRIPTION "Notification failure rate percentage."
    ::= { notificationService 2 }

avgDeliveryMs OBJECT-TYPE
    SYNTAX      Integer32
    MAX-ACCESS  read-only
    STATUS      current
    DESCRIPTION "Average delivery time milliseconds."
    ::= { notificationService 3 }

activeQueues OBJECT-TYPE
    SYNTAX      Integer32
    MAX-ACCESS  read-only
    STATUS      current
    DESCRIPTION "Number of active queues."
    ::= { notificationService 4 }

retryCount OBJECT-TYPE
    SYNTAX      Integer32
    MAX-ACCESS  read-only
    STATUS      current
    DESCRIPTION "Retry count."
    ::= { notificationService 5 }

END
