INVENTORY-SERVICE-MIB DEFINITIONS ::= BEGIN

IMPORTS
    OBJECT-TYPE
        FROM SNMPv2-SMI
    Integer32
        FROM SNMPv2-SMI
    enterprises
        FROM SNMPv2-SMI;

inventoryService OBJECT IDENTIFIER ::= { enterprises 55557 }

stockLevel OBJECT-TYPE
    SYNTAX      Integer32
    MAX-ACCESS  read-only
    STATUS      current
    DESCRIPTION "Stock level."
    ::= { inventoryService 1 }

stockUpdateRate OBJECT-TYPE
    SYNTAX      Integer32
    MAX-ACCESS  read-only
    STATUS      current
    DESCRIPTION "Stock update rate per minute."
    ::= { inventoryService 2 }

stockOutEvents OBJECT-TYPE
    SYNTAX      Integer32
    MAX-ACCESS  read-only
    STATUS      current
    DESCRIPTION "Stock out events count."
    ::= { inventoryService 3 }

inventorySyncErrors OBJECT-TYPE
    SYNTAX      Integer32
    MAX-ACCESS  read-only
    STATUS      current
    DESCRIPTION "Inventory synchronization errors."
    ::= { inventoryService 4 }

avgStockQueryMs OBJECT-TYPE
    SYNTAX      Integer32
    MAX-ACCESS  read-only
    STATUS      current
    DESCRIPTION "Average stock query time milliseconds."
    ::= { inventoryService 5 }

END
